FME workspace merge_bldg_surface.fmwt
Title: merge bldg surface

Parameters:
- SourceDataset_CITYGML =   # Source CityGML File(s)
- DestDataset_FBX =   # Destination FBX Folder
- DestDataset_OBJ =   # Destination OBJ Folder
- SourceDataset_PNGRASTER = $(FME_MF_DIR)1/ground.png   # Source PNG (Portable Network Graphics) File(s)

Readers:
- PNGRASTER_1: PNGRASTER from $(SourceDataset_PNGRASTER)
- CITYGML_1: CITYGML from $(SourceDataset_CITYGML)

Writers:
- FBX_1: FBX to $(DestDataset_FBX)
- OBJ_1: OBJ to $(DestDataset_OBJ)

Note: テクスチャ用PNG画像 / [PNGRASTER] / 最初に読み込むために、 / Navigatorウィンドウで / 最上段に置くこと。
PNGRASTER (reader PNGRASTER_1)
    -> AppearanceStyler
Note: テクスチャのスタイル（張り付け方）設定
AppearanceStyler
    ALPHA = 1.0
    DIFFUSE_COLOR = 1,1,1
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> SharedItemAdder
Note: 共有アイテムライブラリ / に登録してIDを取得
SharedItemAdder
    REF_ATTR = _shared_item_id
    SHARED_TYPE = Texture
    STORAGE_MODE = Add New Item
    -> FeatureMerger_2 [SUPPLIER]
Note: テクスチャなし建物パーツ（MultiSurface） / GroundSurface [CITYGML]
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> FeatureMerger_2 [REQUESTOR]
Note: 無条件に共有アイテムの / IDを結合
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = Yes
    MERGED -> SharedItemIDSetter
Note: IDに基づいて共有アイテム / （この場合はテクスチャ）を設定
SharedItemIDSetter
    REFERENCE_ATTRIBUTE = _shared_item_id
    SHARED_TYPE = Any
    SIDE_TO_SET = Front and Back Sides
    STORAGE_MODE = From Attribute
    TEXTURE_MAPPING_TYPE_CHOICE = Surface Normal
    TEXTURE_U_REPEAT_FACTOR = 1.0
    TEXTURE_V_REPEAT_FACTOR = 1.0
    USE_EXISTING_TEXTURE_COORDINATES = No
    U_ORIGIN_OFFSET = 0.0
    V_ORIGIN_OFFSET = 0.0
    -> Junction
Junction
    -> GeometryCoercer
Note: MultiSurface -> CompositeSurface / Geometry Type: fme_composite_surface
GeometryCoercer
    GQUERY:
      for $geom in //geometry
      where $geom/count(parent::geometry) = 0
      return number($geom/@fme_id)
    KIND = fme_composite_surface
    COERCED -> GeometryCoercer_2
Note: CompositeSurface -> Mesh / Geometry Type: fme_mesh
GeometryCoercer_2
    GQUERY:
      for $geom in //geometry
      where $geom/count(parent::geometry) = 0
      return number($geom/@fme_id)
    KIND = fme_mesh
    COERCED -> MeshMerger
Note: メッシュをマージ
MeshMerger
    ACCUM_INPUT_ATTRS = Use Attributes From One Feature
    GROUP_BY = gml_parent_id
    MESH -> FeatureMerger [SUPPLIER]
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, uro_building_details{}.uro_building_details_uro_serial_number_of_building_certification xml_buffer, uro_building_details{}.uro_building_details_uro_site_area xml_real64, uro_building_details{}.uro_building_details_uro_site_area_units xml_buffer, uro_building_details{}.uro_building_details_uro_building_footprint_area xml_real64, uro_building_details{}.uro_building_details_uro_building_footprint_area_units xml_buffer, uro_building_details{}.uro_building_details_uro_building_roof_edge_area xml_real64, uro_building_details{}.uro_building_details_uro_building_roof_edge_area_units xml_buffer, uro_building_details{}.uro_building_details_uro_development_area xml_real64, uro_building_details{}.uro_building_details_uro_development_area_units xml_buffer, uro_building_details{}.uro_building_details_uro_total_floor_area xml_real64, uro_building_details{}.uro_building_details_uro_total_floor_area_units xml_buffer, uro_building_details{}.uro_building_details_uro_building_structure_type xml_buffer, uro_building_details{}.uro_building_details_uro_building_structure_type_codeSpace xml_buffer, uro_building_details{}.uro_building_details_uro_fireproof_structure_type xml_buffer, uro_building_details{}.uro_building_details_uro_fireproof_structure_type_codeSpace xml_buffer, uro_building_details{}.uro_building_details_uro_implementing_body xml_buffer, uro_building_details{}.uro_building_details_uro_urban_plan_type xml_buffer, uro_building_details{}.uro_building_details_uro_urban_plan_type_codeSpace xml_buffer, uro_building_details{}.uro_building_details_uro_districts_and_zones_type xml_buffer, uro_building_details{}.uro_building_details_uro_districts_and_zones_type_codeSpace xml_buffer,
      uro_building_details{}.uro_building_details_uro_land_use_plan_type xml_buffer, uro_building_details{}.uro_building_details_uro_land_use_plan_type_codeSpace xml_buffer, uro_building_details{}.uro_building_details_uro_area_classification_type xml_buffer, uro_building_details{}.uro_building_details_uro_area_classification_type_codeSpace xml_buffer, uro_building_details{}.uro_building_details_uro_prefecture xml_buffer, uro_building_details{}.uro_building_details_uro_prefecture_codeSpace xml_buffer, uro_building_details{}.uro_building_details_uro_city xml_buffer, uro_building_details{}.uro_building_details_uro_city_codeSpace xml_buffer, uro_building_details{}.uro_building_details_uro_reference xml_buffer, uro_building_details{}.uro_building_details_uro_note xml_buffer, uro_building_details{}.uro_building_details_uro_survey_year xml_buffer, uro_extended_attribute{}.uro_key_value_pair_uro_key xml_buffer, uro_extended_attribute{}.uro_key_value_pair_uro_key_codeSpace xml_buffer, uro_extended_attribute{}.uro_key_value_pair_uro_string_value xml_buffer, uro_extended_attribute{}.uro_key_value_pair_uro_int_value xml_int64, uro_extended_attribute{}.uro_key_value_pair_uro_double_value xml_real64, uro_extended_attribute{}.uro_key_value_pair_uro_code_value xml_buffer, uro_extended_attribute{}.uro_key_value_pair_uro_code_value_codeSpace xml_buffer, uro_extended_attribute{}.uro_key_value_pair_uro_measured_value xml_real64, uro_extended_attribute{}.uro_key_value_pair_uro_measured_value_units xml_buffer, uro_extended_attribute{}.uro_key_value_pair_uro_date_value xml_date, uro_extended_attribute{}.uro_key_value_pair_uro_uri_value xml_buffer, uro_large_customer_facilities{}.uro_large_customer_facilities_uro_class xml_buffer, uro_large_customer_facilities{}.uro_large_customer_facilities_uro_class_codeSpace xml_buffer, uro_large_customer_facilities{}.uro_large_customer_facilities_uro_name xml_buffer, uro_large_customer_facilities{}.uro_large_customer_facilities_uro_capacity xml_int64, uro_large_customer_facilities{}.uro_large_customer_facilities_uro_owner xml_buffer, uro_large_customer_facilities{}.uro_large_customer_facilities_uro_total_floor_area xml_real64, uro_large_customer_facilities{}.uro_large_customer_facilities_uro_total_floor_area_units xml_buffer, uro_large_customer_facilities{}.uro_large_customer_facilities_uro_total_store_floor_area xml_real64,
      uro_large_customer_facilities{}.uro_large_customer_facilities_uro_total_store_floor_area_units xml_buffer, uro_large_customer_facilities{}.uro_large_customer_facilities_uro_inaugural_date xml_date, uro_large_customer_facilities{}.uro_large_customer_facilities_uro_key_tenants xml_buffer, uro_large_customer_facilities{}.uro_large_customer_facilities_uro_availability xml_boolean, uro_large_customer_facilities{}.uro_large_customer_facilities_uro_urban_plan_type xml_buffer, uro_large_customer_facilities{}.uro_large_customer_facilities_uro_urban_plan_type_codeSpace xml_buffer, uro_large_customer_facilities{}.uro_large_customer_facilities_uro_districts_and_zones_type xml_buffer, uro_large_customer_facilities{}.uro_large_customer_facilities_uro_districts_and_zones_type_codeSpace xml_buffer, uro_large_customer_facilities{}.uro_large_customer_facilities_uro_land_use_plan_type xml_buffer, uro_large_customer_facilities{}.uro_large_customer_facilities_uro_land_use_plan_type_codeSpace xml_buffer, uro_large_customer_facilities{}.uro_large_customer_facilities_uro_area_classification_type xml_buffer, uro_large_customer_facilities{}.uro_large_customer_facilities_uro_area_classification_type_codeSpace xml_buffer, uro_large_customer_facilities{}.uro_large_customer_facilities_uro_prefecture xml_buffer, uro_large_customer_facilities{}.uro_large_customer_facilities_uro_prefecture_codeSpace xml_buffer, uro_large_customer_facilities{}.uro_large_customer_facilities_uro_city xml_buffer, uro_large_customer_facilities{}.uro_large_customer_facilities_uro_city_codeSpace xml_buffer, uro_large_customer_facilities{}.uro_large_customer_facilities_uro_reference xml_buffer, uro_large_customer_facilities{}.uro_large_customer_facilities_uro_note xml_buffer, uro_large_customer_facilities{}.uro_large_customer_facilities_uro_survey_year xml_buffer, 建物ID xml_buffer, 地域地区 xml_buffer
    -> FeatureMerger [REQUESTOR]
Note: 建物ごとにジオメトリを集約 / Join On: / Requestor / Supplier / gml_id / gml_parent_id / Merge Parameters: / Feature Merge Type: Geometry / Process Duplicate Suppliers: / Geometry Merge Type: Build Aggregates
FeatureMerger
    GEOM_TYPE = Build Aggregates
    JOIN_KEYS = @Value(gml_id) @Value(gml_parent_id) AUTO
    MERGE_TYPE = Geometry
    PROCESS_DUPS = YES
    REJECT_NULL_MISSING_KEYS = No
    SUPPLIERS_FIRST = No
    MERGED -> CsmapReprojector
Note: 必要に応じて座標系変換
CsmapReprojector
    DEST = JGD2011-09_FME
    INTERPOLATION_TYPE_NAME = Nearest Neighbor
    RASTER_CELL_SIZE = Preserve Cells
    RASTER_TOLERANCE = 0.0
    VERTICAL_HANDLING = Ignore heights and leave them unchanged
    REPROJECTED -> model (writer FBX_1)
    REPROJECTED -> model (writer OBJ_1)
Note: FBXファイルに出力
model (writer FBX_1)
model (writer OBJ_1)

Bookmark: 不使用
Address (reader CITYGML_1)
    attributes: citygml_target_uri xml_buffer, citygml_feature_role xml_buffer, citygml_feature_role_attr_name xml_buffer, citygml_feature_role_attr_val xml_buffer, gml_description xml_buffer, gml_name xml_buffer, citygml_address xml_xml
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer

Bookmark: テクスチャあり建物パーツ
OuterCeilingSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> Junction
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> Junction
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> Junction
