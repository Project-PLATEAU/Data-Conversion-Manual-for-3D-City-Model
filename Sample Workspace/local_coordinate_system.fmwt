FME workspace local_coordinate_system.fmwt
Title: Local Coordinate System

Parameters:
- DestDataset_FBX =   # Destination FBX Folder
- DestDataset_OBJ =   # Destination OBJ Folder
- DestDataset_UDATASMITH =   # Destination UDATASMITH Directory
- DestDataset_IFC =   # Destination Industry Foundation Class (IFC) File(s)

Writers:
- FBX_1: FBX to $(DestDataset_FBX)
- OBJ_1: OBJ to $(DestDataset_OBJ)
- UDATASMITH_1: UDATASMITH to $(DestDataset_UDATASMITH)
- IFC_1: IFC to $(DestDataset_IFC)

fbx (writer FBX_1)
obj (writer OBJ_1)
datasmith (writer UDATASMITH_1)
ifc (writer IFC_1)
