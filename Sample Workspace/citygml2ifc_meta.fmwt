FME workspace citygml2ifc_meta.fmwt
Title: CITYGML to IFC w/metadata

Parameters:
- SourceDataset_CITYGML =   # Source CityGML File(s)
- CODELIST_BUILDING_USAGE_XML = $(FME_MF_DIR)1/codelists/Building_usage.xml   # bldg:usage コードリスト（XML）
- DestDataset_IFC =   # Destination Industry Foundation Class (IFC) File(s)

Readers:
- CITYGML_1: CITYGML from $(SourceDataset_CITYGML)

Writers:
- IFC_1: IFC to $(DestDataset_IFC)

Note: bldg/*.gml [CITYGML]
Note: CityGMLリーダーパラメーター / LODs to Read: LOD 1, LOD 2 / GML SRS Axis Order: 2,1,3
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, uro_building_details{}.uro_building_details_uro_serial_number_of_building_certification xml_buffer, uro_building_details{}.uro_building_details_uro_site_area xml_real64, uro_building_details{}.uro_building_details_uro_site_area_units xml_buffer, uro_building_details{}.uro_building_details_uro_building_footprint_area xml_real64, uro_building_details{}.uro_building_details_uro_building_footprint_area_units xml_buffer, uro_building_details{}.uro_building_details_uro_building_roof_edge_area xml_real64, uro_building_details{}.uro_building_details_uro_building_roof_edge_area_units xml_buffer, uro_building_details{}.uro_building_details_uro_development_area xml_real64, uro_building_details{}.uro_building_details_uro_development_area_units xml_buffer, uro_building_details{}.uro_building_details_uro_total_floor_area xml_real64, uro_building_details{}.uro_building_details_uro_total_floor_area_units xml_buffer, uro_building_details{}.uro_building_details_uro_building_structure_type xml_buffer, uro_building_details{}.uro_building_details_uro_building_structure_type_codeSpace xml_buffer, uro_building_details{}.uro_building_details_uro_fireproof_structure_type xml_buffer, uro_building_details{}.uro_building_details_uro_fireproof_structure_type_codeSpace xml_buffer, uro_building_details{}.uro_building_details_uro_implementing_body xml_buffer, uro_building_details{}.uro_building_details_uro_urban_plan_type xml_buffer, uro_building_details{}.uro_building_details_uro_urban_plan_type_codeSpace xml_buffer, uro_building_details{}.uro_building_details_uro_districts_and_zones_type xml_buffer, uro_building_details{}.uro_building_details_uro_districts_and_zones_type_codeSpace xml_buffer,
      uro_building_details{}.uro_building_details_uro_land_use_plan_type xml_buffer, uro_building_details{}.uro_building_details_uro_land_use_plan_type_codeSpace xml_buffer, uro_building_details{}.uro_building_details_uro_area_classification_type xml_buffer, uro_building_details{}.uro_building_details_uro_area_classification_type_codeSpace xml_buffer, uro_building_details{}.uro_building_details_uro_prefecture xml_buffer, uro_building_details{}.uro_building_details_uro_prefecture_codeSpace xml_buffer, uro_building_details{}.uro_building_details_uro_city xml_buffer, uro_building_details{}.uro_building_details_uro_city_codeSpace xml_buffer, uro_building_details{}.uro_building_details_uro_reference xml_buffer, uro_building_details{}.uro_building_details_uro_note xml_buffer, uro_building_details{}.uro_building_details_uro_survey_year xml_buffer, uro_extended_attribute{}.uro_key_value_pair_uro_key xml_buffer, uro_extended_attribute{}.uro_key_value_pair_uro_key_codeSpace xml_buffer, uro_extended_attribute{}.uro_key_value_pair_uro_string_value xml_buffer, uro_extended_attribute{}.uro_key_value_pair_uro_int_value xml_int64, uro_extended_attribute{}.uro_key_value_pair_uro_double_value xml_real64, uro_extended_attribute{}.uro_key_value_pair_uro_code_value xml_buffer, uro_extended_attribute{}.uro_key_value_pair_uro_code_value_codeSpace xml_buffer, uro_extended_attribute{}.uro_key_value_pair_uro_measured_value xml_real64, uro_extended_attribute{}.uro_key_value_pair_uro_measured_value_units xml_buffer, uro_extended_attribute{}.uro_key_value_pair_uro_date_value xml_date, uro_extended_attribute{}.uro_key_value_pair_uro_uri_value xml_buffer, uro_large_customer_facilities{}.uro_large_customer_facilities_uro_class xml_buffer, uro_large_customer_facilities{}.uro_large_customer_facilities_uro_class_codeSpace xml_buffer, uro_large_customer_facilities{}.uro_large_customer_facilities_uro_name xml_buffer, uro_large_customer_facilities{}.uro_large_customer_facilities_uro_capacity xml_int64, uro_large_customer_facilities{}.uro_large_customer_facilities_uro_owner xml_buffer, uro_large_customer_facilities{}.uro_large_customer_facilities_uro_total_floor_area xml_real64, uro_large_customer_facilities{}.uro_large_customer_facilities_uro_total_floor_area_units xml_buffer, uro_large_customer_facilities{}.uro_large_customer_facilities_uro_total_store_floor_area xml_real64,
      uro_large_customer_facilities{}.uro_large_customer_facilities_uro_total_store_floor_area_units xml_buffer, uro_large_customer_facilities{}.uro_large_customer_facilities_uro_inaugural_date xml_date, uro_large_customer_facilities{}.uro_large_customer_facilities_uro_key_tenants xml_buffer, uro_large_customer_facilities{}.uro_large_customer_facilities_uro_availability xml_boolean, uro_large_customer_facilities{}.uro_large_customer_facilities_uro_urban_plan_type xml_buffer, uro_large_customer_facilities{}.uro_large_customer_facilities_uro_urban_plan_type_codeSpace xml_buffer, uro_large_customer_facilities{}.uro_large_customer_facilities_uro_districts_and_zones_type xml_buffer, uro_large_customer_facilities{}.uro_large_customer_facilities_uro_districts_and_zones_type_codeSpace xml_buffer, uro_large_customer_facilities{}.uro_large_customer_facilities_uro_land_use_plan_type xml_buffer, uro_large_customer_facilities{}.uro_large_customer_facilities_uro_land_use_plan_type_codeSpace xml_buffer, uro_large_customer_facilities{}.uro_large_customer_facilities_uro_area_classification_type xml_buffer, uro_large_customer_facilities{}.uro_large_customer_facilities_uro_area_classification_type_codeSpace xml_buffer, uro_large_customer_facilities{}.uro_large_customer_facilities_uro_prefecture xml_buffer, uro_large_customer_facilities{}.uro_large_customer_facilities_uro_prefecture_codeSpace xml_buffer, uro_large_customer_facilities{}.uro_large_customer_facilities_uro_city xml_buffer, uro_large_customer_facilities{}.uro_large_customer_facilities_uro_city_codeSpace xml_buffer, uro_large_customer_facilities{}.uro_large_customer_facilities_uro_reference xml_buffer, uro_large_customer_facilities{}.uro_large_customer_facilities_uro_note xml_buffer, uro_large_customer_facilities{}.uro_large_customer_facilities_uro_survey_year xml_buffer, 建物ID xml_buffer, 再開発等促進区等を定める地区計画 xml_buffer, 地域地区 xml_buffer, 地区計画 xml_buffer
    -> GeometryPartExtractor
Note: LOD2のジオメトリを抽出 / 抽出条件: ジオメトリ名が"lod2"から始まる
Note: （参考1）ユーザーパラメーターの作成方法 / (1) Navigatorウィンドウで作成 / Navigatorウィンドウの User Parameters/Published Parameters を右クリック / > Create User Parameter を選択 / (2) トランスフォーマーのパラメーターから作成 / トランスフォーマーのパラメーターとリンクするユーザーパラメーターを作成する場合は、次の方法でもできる。 / トランスフォーマーのパラメーター入力フィールドの右にあるメニューボタン▼をクリック / > User Parameter / > Create User Paremter を選択 / このワークスペース例の [CODERLIST_BUIDING_USAGE_XML] パラメーターは (1) 方法、 / [DEST_COORDSYS] パラメーターは (2) の方法で作成した。 / ユーザーパラメーターについての詳細は次のドキュメントを参照 / FME Workbench | Working with User Parameters / https://docs.safe.com/fme/html/FME_Desktop_Documentation/FME_Workbench/Workbench/published_private_parameters.htm
GeometryPartExtractor
    GQUERY:
      for $geom in //geometry
      where starts-with(xs:string($geom/@fme_geometry_name), 'lod2')
      return number($geom/@fme_id)
    EXTRACTED -> GeometryPropertySetter
    UNTOUCHED -> GeometryPartExtractor_2
Note: （参考2）ライターフィーチャータイプの追加方法 / 多くのフォーマットではライターをワークスペースに追加した直後、ライターフィーチャータイプはひとつだけキャンバスに現れるが、 / 複数のフィーチャータイプを定義できるフォーマット（IFCを含む）の場合は、ライターをワークスペースに追加した後 / キャンバス上の右クリック > Insert Writer Feature Type / でライターフィーチャータイプを追加することができる。 / このワークスペース例では、IFCライターを追加するのと同時に「IfcSlab」フィーチャータイプを追加し、その後、 / 上記の方法で「IfcSite」フィーチャータイプを追加した。 / FMEのIFCライターがサポートしているフィーチャータイプについては、ドキュメントの次のページ参照。 / https://docs.safe.com/fme/html/FME_Desktop_Documentation/FME_ReadersWriters/ifc/Feature_Representation.htm
Note: LOD2がなかた建物から / LOD1のジオメトリを抽出 / 抽出条件: ジオメトリ名が"lod1"から始まる
GeometryPartExtractor_2
    GQUERY:
      for $geom in //geometry
      where starts-with(xs:string($geom/@fme_geometry_name), 'lod1')
      return number($geom/@fme_id)
    EXTRACTED -> GeometryPropertySetter
Note: ジオメトリ名を"Body"で上書きする
GeometryPropertySetter
    GEOM_NAME_FIELD = Body
    GQUERY:
      for $geom in //geometry
      where $geom/count(parent::geometry) = 0
      return number($geom/@fme_id)
    OVERWRITE_CHOICE = Yes
    SETTYPE_PARAM = Geometry Name
    SET -> XMLXQueryExtractor
Note: bldg:usage の値（コード） / に対応する文字列を / コードリストから取得する
Note: CityGMLのXMlスキーマでは、bldg:usage の多重度は 0..* となっており、複数回出現する / （つまり、一つの建物が複数の用途をもつ）場合がある。 / FME CityGMLリーダーは、2以上の多重度のデータをリスト属性（bldg:usage の場合は / citygml_usage{}）として読み込む。 / XMLXQueryExtractor では、次の処理を行っている。 / (1) 別のコード（citygml_usage{0}, citygml_usage{1}, ...）を抽出 / (2) それらをコードリスト（Building_usage.xml）に基づいて意味文字列に変換 / (3) それらを特定の文字（例えばスペース）区切りで連結した単一の文字列値を作成し / (4) Description属性に格納する。 / 主要なパラメーター / (1) XQuery式から参照するXMLドキュメントの指定 / XML Source: / XML Input: XML file (外部ファイルを指定する) / XML File: $(CODELIST_BUILDING_USAGE_XML) (ファイルパス) / ※[CODELIST_BUILDING_USAGE_XML]はユーザーパラメーター名 / このパラメーターは、Navigatorウィンドウの User Parameters/Published Parameters で / Filename(Existing) タイプのパラメーターとして作成、追加した。 / (2) XQuery式 / XQuery Expression: / declare namespace gml="http://www.opengis.net/gml"; / for $u in fme:get-list-attribute('citygml_usage{}') / return data(//gml:Definition[data(child::gml:name) = $u]/gml:description) / citygml_usage{} リストの各要素（コード値）について、コードリストXMLの各エントリーのうち、 / 当該コードが gml:Definition/gml:name と一致する gml:Definition/gml_description / の値を取得してシーケンス (値1, 値2, ...) として返す。 / (3) 結果の出力方法の設定 / Results: / Return Value: Separated values (XQueryが返したシーケンスの個別の値を列挙する) / Result Attribute: Description (値を格納する属性名) / Separator Character(s): <スペース> (個別の値間の区切り文字）
XMLXQueryExtractor
    QUERY_EXPR:
      declare namespace gml="http://www.opengis.net/gml";
      for $u in fme:get-list-attribute('citygml_usage{}')
      return data(//gml:Definition[data(child::gml:name) = $u]/gml:description)
    RESULT_ATTRIBUTE = Description
    RESULT_TYPE_NAME = Separated values
    SEPARATOR_VALUE = " "
    WRITE_XML_HEADER = No
    XML_FILE = $(CODELIST_BUILDING_USAGE_XML)
    XML_TYPE = XML file
    XQUERY_TYPE = XQuery expression
    QUERY_RESULTS -> CsmapReprojector
Note: 必要に応じて座標系変換
CsmapReprojector
    DEST = JGD2011-09_FME
    INTERPOLATION_TYPE_NAME = Nearest Neighbor
    RASTER_CELL_SIZE = Preserve Cells
    RASTER_TOLERANCE = 0.0
    VERTICAL_HANDLING = Ignore heights and leave them unchanged
    REPROJECTED -> IfcSlab (writer IFC_1)
IfcSlab (writer IFC_1)
    attributes: Description string

Bookmark: bldg 不使用
OuterCeilingSurface (reader CITYGML_1)
    attributes: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
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
Address (reader CITYGML_1)
    attributes: citygml_target_uri xml_buffer, citygml_feature_role xml_buffer, citygml_feature_role_attr_name xml_buffer, citygml_feature_role_attr_val xml_buffer, gml_description xml_buffer, gml_name xml_buffer, citygml_address xml_xml
GroundSurface (reader CITYGML_1)
    attributes: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
RoofSurface (reader CITYGML_1)
    attributes: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
WallSurface (reader CITYGML_1)
    attributes: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
