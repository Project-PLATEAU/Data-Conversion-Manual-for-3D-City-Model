FME workspace search_envelope.fmwt
Title: Search Envelope

Parameters:
- SourceDataset_CITYGML =   # Source CityGML File(s)

Readers:
- CITYGML_1: CITYGML from $(SourceDataset_CITYGML)

Address (reader CITYGML_1)
    attributes: citygml_target_uri xml_buffer, citygml_feature_role xml_buffer, citygml_feature_role_attr_name xml_buffer, citygml_feature_role_attr_val xml_buffer, gml_description xml_buffer, gml_name xml_buffer, citygml_address xml_xml
Building (reader CITYGML_1)
    attributes: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
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
GroundSurface (reader CITYGML_1)
    attributes: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
OuterCeilingSurface (reader CITYGML_1)
    attributes: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
RoofSurface (reader CITYGML_1)
    attributes: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
WallSurface (reader CITYGML_1)
    attributes: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
