FME workspace citygml2datasmith.fmwt
Title: CityGML to Datasmith

Parameters:
- SourceDataset_CITYGML =   # Source CityGML File(s)
- SourceDataset_CITYGML_3 =   # Source CityGML File(s)
- DestDataset_UDATASMITH =   # Destination UDATASMITH Directory
- DestDataset_UDATASMITH_5 =   # Destination UDATASMITH Directory
- DestDataset_UDATASMITH_4 =   # Destination UDATASMITH Directory

Readers:
- CITYGML_1: CITYGML from $(SourceDataset_CITYGML)
- CITYGML_2: CITYGML from $(SourceDataset_CITYGML_3)

Writers:
- UDATASMITH_1: UDATASMITH to $(DestDataset_UDATASMITH)
- UDATASMITH_2: UDATASMITH to $(DestDataset_UDATASMITH_4)
- UDATASMITH_3: UDATASMITH to $(DestDataset_UDATASMITH_5)

Note: LOD2のジオメトリを抽出 / 抽出条件: ジオメトリ名が"lod2"から始まる
GeometryPartExtractor
    GQUERY:
      for $geom in //geometry
      where starts-with(xs:string($geom/@fme_geometry_name), 'lod2')
      return number($geom/@fme_id)
    EXTRACTED -> FeatureMerger [REQUESTOR]
    UNTOUCHED -> GeometryPartExtractor_2
Note: 建物ごとにジオメトリを集約 / Join On: / Requestor / Supplier / gml_id / gml_parent_id / Merge Parameters: / Feature Merge Type: Geometry / Process Duplicate Suppliers: / Geometry Merge Type: Build Aggregates
FeatureMerger
    GEOM_TYPE = Build Aggregates
    JOIN_KEYS = @Value(gml_id) @Value(gml_parent_id) AUTO
    MERGE_TYPE = Geometry
    PROCESS_DUPS = YES
    REJECT_NULL_MISSING_KEYS = No
    SUPPLIERS_FIRST = No
    MERGED -> CsmapReprojector
Note: LOD2のない建物から / LOD1のジオメトリを抽出 / 抽出条件: ジオメトリ名が"lod1"から始まる
GeometryPartExtractor_2
    GQUERY:
      for $geom in //geometry
      where starts-with(xs:string($geom/@fme_geometry_name), 'lod1')
      return number($geom/@fme_id)
    EXTRACTED -> CsmapReprojector_2
GeometryCoercer
    GQUERY:
      for $geom in //geometry
      where $geom/count(parent::geometry) = 0
      return number($geom/@fme_id)
    KIND = fme_mesh
    COERCED -> CsmapReprojector_3

Bookmark: 建物データ(bldg)
OuterCeilingSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> FeatureMerger [SUPPLIER]
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> FeatureMerger [SUPPLIER]
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> FeatureMerger [SUPPLIER]
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> FeatureMerger [SUPPLIER]
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, uro_building_details{}.uro_building_details_uro_serial_number_of_building_certification xml_buffer, uro_building_details{}.uro_building_details_uro_site_area xml_real64, uro_building_details{}.uro_building_details_uro_site_area_units xml_buffer, uro_building_details{}.uro_building_details_uro_building_footprint_area xml_real64, uro_building_details{}.uro_building_details_uro_building_footprint_area_units xml_buffer, uro_building_details{}.uro_building_details_uro_building_roof_edge_area xml_real64, uro_building_details{}.uro_building_details_uro_building_roof_edge_area_units xml_buffer, uro_building_details{}.uro_building_details_uro_development_area xml_real64, uro_building_details{}.uro_building_details_uro_development_area_units xml_buffer, uro_building_details{}.uro_building_details_uro_total_floor_area xml_real64, uro_building_details{}.uro_building_details_uro_total_floor_area_units xml_buffer, uro_building_details{}.uro_building_details_uro_building_structure_type xml_buffer, uro_building_details{}.uro_building_details_uro_building_structure_type_codeSpace xml_buffer, uro_building_details{}.uro_building_details_uro_fireproof_structure_type xml_buffer, uro_building_details{}.uro_building_details_uro_fireproof_structure_type_codeSpace xml_buffer, uro_building_details{}.uro_building_details_uro_implementing_body xml_buffer, uro_building_details{}.uro_building_details_uro_urban_plan_type xml_buffer, uro_building_details{}.uro_building_details_uro_urban_plan_type_codeSpace xml_buffer, uro_building_details{}.uro_building_details_uro_districts_and_zones_type xml_buffer, uro_building_details{}.uro_building_details_uro_districts_and_zones_type_codeSpace xml_buffer,
      uro_building_details{}.uro_building_details_uro_land_use_plan_type xml_buffer, uro_building_details{}.uro_building_details_uro_land_use_plan_type_codeSpace xml_buffer, uro_building_details{}.uro_building_details_uro_area_classification_type xml_buffer, uro_building_details{}.uro_building_details_uro_area_classification_type_codeSpace xml_buffer, uro_building_details{}.uro_building_details_uro_prefecture xml_buffer, uro_building_details{}.uro_building_details_uro_prefecture_codeSpace xml_buffer, uro_building_details{}.uro_building_details_uro_city xml_buffer, uro_building_details{}.uro_building_details_uro_city_codeSpace xml_buffer, uro_building_details{}.uro_building_details_uro_reference xml_buffer, uro_building_details{}.uro_building_details_uro_note xml_buffer, uro_building_details{}.uro_building_details_uro_survey_year xml_buffer, uro_extended_attribute{}.uro_key_value_pair_uro_key xml_buffer, uro_extended_attribute{}.uro_key_value_pair_uro_key_codeSpace xml_buffer, uro_extended_attribute{}.uro_key_value_pair_uro_string_value xml_buffer, uro_extended_attribute{}.uro_key_value_pair_uro_int_value xml_int64, uro_extended_attribute{}.uro_key_value_pair_uro_double_value xml_real64, uro_extended_attribute{}.uro_key_value_pair_uro_code_value xml_buffer, uro_extended_attribute{}.uro_key_value_pair_uro_code_value_codeSpace xml_buffer, uro_extended_attribute{}.uro_key_value_pair_uro_measured_value xml_real64, uro_extended_attribute{}.uro_key_value_pair_uro_measured_value_units xml_buffer, uro_extended_attribute{}.uro_key_value_pair_uro_date_value xml_date, uro_extended_attribute{}.uro_key_value_pair_uro_uri_value xml_buffer, uro_large_customer_facilities{}.uro_large_customer_facilities_uro_class xml_buffer, uro_large_customer_facilities{}.uro_large_customer_facilities_uro_class_codeSpace xml_buffer, uro_large_customer_facilities{}.uro_large_customer_facilities_uro_name xml_buffer, uro_large_customer_facilities{}.uro_large_customer_facilities_uro_capacity xml_int64, uro_large_customer_facilities{}.uro_large_customer_facilities_uro_owner xml_buffer, uro_large_customer_facilities{}.uro_large_customer_facilities_uro_total_floor_area xml_real64, uro_large_customer_facilities{}.uro_large_customer_facilities_uro_total_floor_area_units xml_buffer, uro_large_customer_facilities{}.uro_large_customer_facilities_uro_total_store_floor_area xml_real64,
      uro_large_customer_facilities{}.uro_large_customer_facilities_uro_total_store_floor_area_units xml_buffer, uro_large_customer_facilities{}.uro_large_customer_facilities_uro_inaugural_date xml_date, uro_large_customer_facilities{}.uro_large_customer_facilities_uro_key_tenants xml_buffer, uro_large_customer_facilities{}.uro_large_customer_facilities_uro_availability xml_boolean, uro_large_customer_facilities{}.uro_large_customer_facilities_uro_urban_plan_type xml_buffer, uro_large_customer_facilities{}.uro_large_customer_facilities_uro_urban_plan_type_codeSpace xml_buffer, uro_large_customer_facilities{}.uro_large_customer_facilities_uro_districts_and_zones_type xml_buffer, uro_large_customer_facilities{}.uro_large_customer_facilities_uro_districts_and_zones_type_codeSpace xml_buffer, uro_large_customer_facilities{}.uro_large_customer_facilities_uro_land_use_plan_type xml_buffer, uro_large_customer_facilities{}.uro_large_customer_facilities_uro_land_use_plan_type_codeSpace xml_buffer, uro_large_customer_facilities{}.uro_large_customer_facilities_uro_area_classification_type xml_buffer, uro_large_customer_facilities{}.uro_large_customer_facilities_uro_area_classification_type_codeSpace xml_buffer, uro_large_customer_facilities{}.uro_large_customer_facilities_uro_prefecture xml_buffer, uro_large_customer_facilities{}.uro_large_customer_facilities_uro_prefecture_codeSpace xml_buffer, uro_large_customer_facilities{}.uro_large_customer_facilities_uro_city xml_buffer, uro_large_customer_facilities{}.uro_large_customer_facilities_uro_city_codeSpace xml_buffer, uro_large_customer_facilities{}.uro_large_customer_facilities_uro_reference xml_buffer, uro_large_customer_facilities{}.uro_large_customer_facilities_uro_note xml_buffer, uro_large_customer_facilities{}.uro_large_customer_facilities_uro_survey_year xml_buffer, 建物ID xml_buffer, 地域地区 xml_buffer
    -> GeometryPartExtractor
Address (reader CITYGML_1)
    attributes: citygml_target_uri xml_buffer, citygml_feature_role xml_buffer, citygml_feature_role_attr_name xml_buffer, citygml_feature_role_attr_val xml_buffer, gml_description xml_buffer, gml_name xml_buffer, citygml_address xml_xml

Bookmark: 座標変換
Note: 必要に応じて座標系変換
CsmapReprojector
    DEST = JGD2011-09_FME
    INTERPOLATION_TYPE_NAME = Nearest Neighbor
    RASTER_CELL_SIZE = Preserve Cells
    RASTER_TOLERANCE = 0.0
    VERTICAL_HANDLING = Ignore heights and leave them unchanged
    REPROJECTED -> lod2 (writer UDATASMITH_1)
Note: 必要に応じて座標系変換
CsmapReprojector_2
    DEST = JGD2011-09_FME
    INTERPOLATION_TYPE_NAME = Nearest Neighbor
    RASTER_CELL_SIZE = Preserve Cells
    RASTER_TOLERANCE = 0.0
    VERTICAL_HANDLING = Ignore heights and leave them unchanged
    REPROJECTED -> lod1 (writer UDATASMITH_2)
CsmapReprojector_3
    DEST = JGD2011-09_FME
    INTERPOLATION_TYPE_NAME = Nearest Neighbor
    RASTER_CELL_SIZE = Preserve Cells
    RASTER_TOLERANCE = 0.0
    VERTICAL_HANDLING = Ignore heights and leave them unchanged
    REPROJECTED -> dem (writer UDATASMITH_3)

Bookmark: datasmith出力
Note: LOD2データをdatasmithファイルに出力
lod2 (writer UDATASMITH_1)
Note: LOD1データをdatasmithファイルに出力
lod1 (writer UDATASMITH_2)
Note: demデータをdatasmithファイルに出力
dem (writer UDATASMITH_3)

Bookmark: 地形データ(demo)
TINRelief (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer
    -> GeometryCoercer
ReliefFeature (reader CITYGML_2)
    attributes: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
CityModel (reader CITYGML_2)
    attributes: citygml_target_uri xml_buffer, gml_description xml_buffer, gml_name xml_buffer, citygml_city_object_member{}.xlink_href xml_buffer, citygml_appearance_member{}.xlink_href xml_buffer, gml_feature_member{}.xlink_href xml_buffer
