FME workspace tingenerator.fmwt
Title: TINgenerator

Parameters:
- SourceDataset_CITYGML =   # Source CityGML File(s)
- DestDataset_FBX_3 =   # Destination FBX Folder

Readers:
- CITYGML_1: CITYGML from $(SourceDataset_CITYGML)

Writers:
- FBX_1: FBX to $(DestDataset_FBX_3)

TINRelief (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer
    -> TINGenerator [POINTS/LINES]
Note: Surface Toleranceの値を0より大きくすることでメッシュの頂点を間引くことができる
TINGenerator
    TOLERANCE = 20000
    TIN_SURFACE -> CsmapReprojector
CsmapReprojector
    DEST = JGD2011-09_FME
    INTERPOLATION_TYPE_NAME = Nearest Neighbor
    RASTER_CELL_SIZE = Preserve Cells
    RASTER_TOLERANCE = 0.0
    VERTICAL_HANDLING = Ignore heights and leave them unchanged
    REPROJECTED -> dem (writer FBX_1)
dem (writer FBX_1)
ReliefFeature (reader CITYGML_1)
    attributes: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
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
